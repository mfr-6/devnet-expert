module vlan-service {
  namespace "http://cisco.com/example/vlanservice";
  prefix vlan-service;

  import ietf-inet-types {
    prefix inet;
  }
  import tailf-ncs {
    prefix ncs;
  }
  import tailf-common {
    prefix tailf;
  }

  description "This is my another service package";

  revision 2024-03-31 {
    description
      "Initial revision";
  }

  list vlan-service {
    key name;
    unique vlan-id;

    uses ncs:service-data;
    ncs:servicepoint "vlan-service";

    leaf name {
      tailf:info "VLAN Service instance name";
      type string;
    }

    leaf vlan-id {
      tailf:info "Unique VLAN ID";
      type uint32 {
        range "1..4094";
      }
    }

    list device {
      tailf:info "Device to apply VLAN";
      key name;
      
      leaf name {
        tailf:info "Device name";
        type leafref {
          path "/ncs:devices/ncs:device/ncs:name";
        }
      }

      list interface {
        tailf:info "Ethernet interface";
        key "intf-type intf-id";

        leaf intf-type {
          tailf:info "Etthernet Interface Type";
          type enumeration {
            enum Ethernet;
            enum FastEthernet;
            enum GigabitEthernet;
          }
        }

        leaf intf-id {
          tailf:info "Interface ID";
          type string;
        }
      }
    }


  }
}
